module ietf-bgp-communities {
  yang-version 1.1;
  namespace
    "urn:ietf:params:xml:ns:yang:ietf-bgp-communities";
  prefix bgp-comm;

  import ietf-inet-types {
    prefix inet;
    reference
      "draft-ietf-netmod-rfc6991-bis-17: Common YANG Data Types";
  }

  organization
    "IETF GROW Working Group";
  contact
    "WG Web:   <https://datatracker.ietf.org/wg/grow/>
     WG List:  <mailto:grow@ietf.org>

     Author:   Martin Pels
       <mailto:mpels@ripe.net>";
  description
    "This module describes a structure for BGP Communities

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC YYYY; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC-EDITOR: please update YYYY with this RFC ID

  revision 2025-06-13 {
    description
      "Initial revision.";
    reference
      "RFC YYYY: A YANG Data Model for BGP Communities
       RFC-EDITOR: please update YYYY with this RFC ID";
  }

  typedef two-octet-as-number {
    type uint16;
    description
      "This type represents autonomous system numbers, which
       identify an Autonomous System (AS).

       Autonomous system numbers were originally limited to 16
       bits.  BGP extensions have enlarged the autonomous system
       number space to 32 bits.  The two-octet-as-number type uses
       an uint16 base type for use cases where the enlarged number
       space is not supported.";
    reference
      "RFC 1930: Guidelines for creation, selection, and
       registration of an Autonomous System (AS)";
  }

  typedef community-name {
    type string {
      length "1..255";
      pattern '[^\s]+';
    }
    description
      "This type restricts values for the name of a BGP community.";
    reference
      "RFC YYYY: A YANG Data Model for BGP Communities
       RFC-EDITOR: please update YYYY with this RFC ID";
  }

  typedef community-category {
    type enumeration {
      enum informational {
        value 0;
        description
          "Informational community";
      }
      enum action {
        value 1;
        description
          "Action community";
      }
    }
    description
      "This type restricts values for the category of a BGP
       community.";
    reference
      "RFC 8195: Use of BGP Large Communities";
  }

  typedef community-description {
    type string {
      length "1..65535";
    }
    description
      "This type restricts values for the description of a BGP
       community.";
    reference
      "RFC YYYY: A YANG Data Model for BGP Communities
       RFC-EDITOR: please update YYYY with this RFC ID";
  }

  typedef local-admin-format {
    type enumeration {
      enum decimal {
        value 0;
        description
          "Decimal number string";
      }
      enum binary {
        value 1;
        description
          "Bit string";
      }
    }
    description
      "This type defines the format options for a BGP community
       Local Administrator/Local Data field encoding";
    reference
      "RFC YYYY: A YANG Data Model for BGP Communities
       RFC-EDITOR: please update YYYY with this RFC ID";
  }

  typedef field-name {
    type string {
      length "1..255";
      pattern '[^\s]+';
    }
    description
      "This type restricts values for the name leaf of a BGP
       community Local Administrator/Local Data field.";
    reference
      "RFC YYYY: A YANG Data Model for BGP Communities
       RFC-EDITOR: please update YYYY with this RFC ID";
  }

  typedef field-pattern {
    type string {
      length "1..4095";
      pattern '[-0-9.,*?^$+|(){}\[\]]+';
    }
    description
      "This type restricts values for the pattern leaf of a BGP
       community Local Administrator/Local Data field.  Patterns
       are described as POSIX Extended Regular Expressions";
    reference
      "IEEE 1003.2-1992: Information Technology - Portable
       Operating System Interface (POSIX) - Part 2: Shell and
       Utilities (Vol. 1)";
  }

  typedef field-description {
    type string {
      length "1..65535";
      pattern '(\*)|([^*]+)';
    }
    description
      "This type restricts values for the description leaf of a BGP
       community Local Administrator/Local Data field.  The string
       containing a single asterisk '*' indicates that the value of
       the field should be used as description.";
    reference
      "RFC YYYY: A YANG Data Model for BGP Communities
       RFC-EDITOR: please update YYYY with this RFC ID";
  }

  grouping local-admin-fields {
    description
      "A group of subfields inside the Local Administrator/Local
       Data section of a BGP Community";
    list field {
      key "name";
      ordered-by user;
      description
        "Ordered list of fields with their meanings";
      leaf name {
        type field-name;
        description
          "The name of the field";
      }
      leaf length {
        type uint8;
        description
          "Length of the field.  If local-admin-format is 'decimal',
           this is a number of digits.  In case local-admin-format is
           'binary', it is a number of bits.

           Parsers use the field length to determine how many
           decimals or bits from the Local Administrator part of the
           community are used by this field.  If this leaf is not
           defined, the length is assumed to be the maximum allowed
           length of the entire field list.  In this case the field
           list MUST NOT contain more than one element.";
      }
      leaf pattern {
        type field-pattern;
        mandatory true;
        description
          "Used by parsers to match on the content of the field.
           This could be a single value or a regular expression
           pattern matching multiple values.";
      }
      leaf description {
        type field-description;
        description
          "A text description of the field pattern.  This description
           can be used to provide meaning to specific values for a
           field.";
      }
    }
  }

  container bgp-communities {
    config false;
    description
      "A community set";
    leaf serial {
      type uint32;
      must "boolean(.)";
      description
        "Version number of the community set.  This value wraps and
         should be compared using sequence space arithmetic.
         Publishing implementations are free to decide how to
         generate this value.  One example method is to use the
         YYYYMMDDnn syntax as commonly used inside the DNS.";
      reference
        "RFC 1912: Common DNS Operational and Configuration Errors";
    }
    leaf uri {
      type inet:uri;
      description
        "Publication point for the community set";
    }
    leaf description {
      type string {
        length "1..65535";
      }
      description
        "A description for the community set";
    }
    leaf contact-url {
      type inet:uri;
      description
        "A reference to a webpage with maintainer contact
         information";
    }
    list contact {
      key "email-address";
      description
        "A list of contacts for the community set maintainer(s)";
      leaf email-address {
        type inet:email-address;
        description
          "Maintainer contact e-mail address";
      }
      leaf name {
        type string {
          length "1..255";
        }
        description
          "Maintainer contact name";
      }
      leaf role {
        type string {
          length "1..255";
        }
        description
          "Maintainer contact role";
      }
      leaf organization {
        type string {
          length "1..255";
        }
        description
          "Maintainer contact organization";
      }
      leaf organizational-unit {
        type string {
          length "1..255";
        }
        description
          "Maintainer contact organizational unit";
      }
    }
    list regular {
      key "name";
      ordered-by user;
      description
        "A list of objects describing RFC 1997 BGP Communities";
      leaf name {
        type community-name;
        description
          "Community name";
      }
      leaf category {
        type community-category;
        description
          "Category of the community";
      }
      leaf description {
        type community-description;
        description
          "Description for the community";
      }
      leaf global-admin {
        type two-octet-as-number;
        mandatory true;
        description
          "Global Administrator field";
      }
      container local-admin {
        description
          "Local Administrator Field";
        leaf format {
          type local-admin-format;
          default "decimal";
          description
            "Format used for parsing Local Administrator subfields";
        }
        uses local-admin-fields;
      }
      reference
        "RFC 1997: BGP Communities Attribute";
    }
    list extended {
      key "name";
      ordered-by user;
      description
        "A list of objects describing RFC 4360 Extended BGP
         Communities.  Two-Octet and Four-Octet AS Specific
         communities are supported by this model.";
      leaf name {
        type community-name;
        description
          "Community name";
      }
      leaf category {
        type community-category;
        description
          "Category of the community";
      }
      leaf description {
        type community-description;
        description
          "Description for the community";
      }
      leaf type {
        type uint8;
        mandatory true;
        description
          "High-order Type of the community.  Supported values are 0
           (0x00) for Transitive Two-Octet AS-Specific Extended
           Communities, 2 (0x02) for Transitive Four-Octet
           AS-Specific Extended Communities, 64 (0x40) for
           Non-Transitive Two-Octet AS-Specific Extended Communities
           and 66 (0x42) for Non-Transitive Four-Octet AS-Specific
           Extended Communities.";
      }
      leaf subtype {
        type uint8;
        mandatory true;
        description
          "Low-order Sub-Type of the community";
      }
      choice global-admin {
        mandatory true;
        description
          "Global Administrator Field";
        case asn {
          leaf asn {
            type two-octet-as-number;
            must "../type = 0 or ../type = 64";
            description
              "Two-Octet AS";
          }
        }
        case asn4 {
          leaf asn4 {
            type inet:as-number;
            must "../type = 2 or ../type = 66";
            description
              "Four-Octet AS";
          }
        }
      }
      container local-admin {
        description
          "Local Administrator Field";
        leaf format {
          type local-admin-format;
          default "decimal";
          description
            "Format used for parsing Local Administrator subfields";
        }
        uses local-admin-fields;
      }
      reference
        "RFC 4360: BGP Extended Communities Attribute";
    }
    list large {
      key "name";
      ordered-by user;
      description
        "A list of objects describing RFC 8092 Large BGP
         Communities";
      leaf name {
        type community-name;
        description
          "Community name";
      }
      leaf category {
        type community-category;
        description
          "Category of the community";
      }
      leaf description {
        type community-description;
        description
          "Description for the community";
      }
      leaf global-admin {
        type inet:as-number;
        mandatory true;
        description
          "Global Administrator field";
      }
      container local-data-part-1 {
        description
          "Local Data Part 1 Field";
        leaf format {
          type local-admin-format;
          default "decimal";
          description
            "Format used for parsing Local Data Part 1 subfields";
        }
        uses local-admin-fields;
      }
      container local-data-part-2 {
        description
          "Local Data Part 2 Field";
        leaf format {
          type local-admin-format;
          default "decimal";
          description
            "Format used for parsing Local Data Part 2 subfields";
        }
        uses local-admin-fields;
      }
      reference
        "RFC 8092: BGP Large Communities Attribute";
    }
  }
}
