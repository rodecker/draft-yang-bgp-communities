module draft-ietf-grow-yang-bgp-communities {

  yang-version 1.1;

  namespace "urn:to-be-defined";

  prefix bgpcomm;

  organization
    "To be defined";

  contact
    "To be defined";

  description
    "This module describes a structure for BGP Communities";

  revision "2023-08-01" {
    description
      "Initial version.";
    reference "0.0.2";
  }

  grouping localadmin-fields {
    list fields {
      ordered-by user;
      key "name";

      leaf name {
        type string {
          length "1..255";
          pattern "[^ \t\n]+";
        }
        mandatory "true";
        description
          "The name of the field";
      }

      leaf length {
        type uint8;
        description
          "Length of the field";
      }

      leaf pattern {
        type string;
        mandatory "true";
        description
          "Regular Expression describing the expected contents of the field";
      }

      leaf description {
        type string;
        description
          "A text description of the field contents";
      }
    }
  }

  container bgp-communities {

    leaf serial {
      type "uint32";
      mandatory "true";
      description
        "Version number of the community set.";
    }

    leaf uri {
      type string;
      description
        "Publication point for the community set";
    }

    leaf description {
      type string;
      description
        "A description for the community set";
    }

    leaf contacturl {
      type string;
      description
        "A reference to a webpage with maintainer contact information";
    }

    list contacts {
      key "emailaddress";

      leaf emailaddress {
        type string;
        description
          "Maintainer contact e-mail address";
      }

      leaf name {
        type string;
        description
          "Maintainer contact name";
      }

      leaf role {
        type string;
        description
          "Maintainer contact role";
      }

      leaf organization {
        type string;
        description
          "Maintainer contact organization";
      }

      leaf organizationalunit {
        type string;
        description
          "Maintainer contact organizational unit";
      }
    }

    list regular {
      key "name";

      leaf name {
        type string {
          length 1..255;
          pattern "[^ \t\n]+";
        }
        mandatory "true";
        description
          "Community name.";
      }

      leaf description {
        type string;
        description
          "Description for the community";
      }

      leaf globaladmin {
        type "uint16";
        mandatory "true";
        description
          "Global Administrator field";
      }

      container localadmin {
        leaf format {
          type "string" {
            pattern
              'decimal|binary';
          }
          default "decimal";
          description
            "Format used for parsing localadmin fields";
        }

        uses localadmin-fields;
      }
    }

    list extended {
      key "name";

      leaf name {
        type string {
          length 1..255;
          pattern "[^ \t\n]+";
        }
        mandatory "true";
        description
          "Community name";
      }

      leaf description {
        type string;
        description
          "Description for the community";
      }

      leaf type {
        type uint8;
        mandatory "true";
        description
          "Type Field";
      }
      leaf subtype {
        type uint8;
        mandatory "true";
        description
          "Sub-Type Field";
      }

      choice globaladmin {
        mandatory "true";
        case asn {
          leaf asn {
            type "uint16";
            description
              "Two-Octet AS";
          }
        }
        case asn4 {
          leaf asn4 {
            type "uint32";
            description
              "Four-Octet AS";
          }
        }
      }

      container localadmin {
        leaf format {
          type "string" {
            pattern
              'decimal|binary';
          }
          default "decimal";
          description
            "Format used for parsing localadmin fields";
        }

        uses localadmin-fields;
      }
    }

    list large {
      key "name";

      leaf name {
        type string {
          length 1..255;
          pattern "[^ \t\n]+";
        }
        mandatory "true";
        description
          "Community name.";
      }

      leaf description {
        type string;
        description
          "Description for the community";
      }

      leaf globaladmin {
        type "uint32";
        mandatory "true";
        description
          "Global Administrator field";
      }

      container localdatapart1 {
        leaf format {
          type "string" {
            pattern
              'decimal|binary';
          }
          default "decimal";
          description
            "Format used for parsing localadmin fields";
        }

        uses localadmin-fields;
      }

      container localdatapart2 {
        leaf format {
          type "string" {
            pattern
              'decimal|binary';
          }
          default "decimal";
          description
            "Format used for parsing localadmin fields";
        }

        uses localadmin-fields;
      }
    }
  }
}
